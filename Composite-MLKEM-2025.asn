Composite-MLKEM-2025
      { iso(1) identified-organization(3) dod(6) internet(1) 
        security(5) mechanisms(5) pkix(7) id-mod(0) 
        id-mod-composite-mlkem-2025(TBDMOD) }

DEFINITIONS IMPLICIT TAGS ::= BEGIN

EXPORTS ALL;

IMPORTS

PUBLIC-KEY, AlgorithmIdentifier{}, SMIME-CAPS
  FROM AlgorithmInformation-2009  -- RFC 5912 [X509ASN1]
      { iso(1) identified-organization(3) dod(6) internet(1)
        security(5) mechanisms(5) pkix(7) id-mod(0)
        id-mod-algorithmInformation-02(58) }

KEM-ALGORITHM
  FROM KEMAlgorithmInformation-2023
      { iso(1) identified-organization(3) dod(6) internet(1)
        security(5) mechanisms(5) pkix(7) id-mod(0)
        id-mod-kemAlgorithmInformation-2023(109) }
;


--
-- Object Identifiers
--

--
-- Information Object Classes
--

pk-CompositeKEM {OBJECT IDENTIFIER:id}
  PUBLIC-KEY ::= {
    IDENTIFIER id
    -- KEY no ASN.1 wrapping --
    PARAMS ARE absent
    CERT-KEY-USAGE { keyEncipherment }
    -- PRIVATE-KEY no ASN.1 wrapping --
  }

kema-CompositeKEM {
  OBJECT IDENTIFIER:id,
    PUBLIC-KEY:publicKeyType }
    KEM-ALGORITHM ::= {
         IDENTIFIER id
         -- VALUE no ASN.1 wrapping --
         PARAMS ARE absent
         PUBLIC-KEYS { publicKeyType }
         SMIME-CAPS { IDENTIFIED BY id }
        }



--
-- Composite KEM Algorithms
--


-- Composite ML-KEM

id-MLKEM768-RSA2048-SHA3-256 OBJECT IDENTIFIER ::= {
   iso(1) identified-organization(3) dod(6) internet(1) security(5)
   mechanisms(5) pkix(7) alg(6) 55 }

pk-MLKEM768-RSA2048-SHA3-256 PUBLIC-KEY ::= 
  pk-CompositeKEM { 
    id-MLKEM768-RSA2048-SHA3-256 }

kema-MLKEM768-RSA2048-SHA3-256 KEM-ALGORITHM ::= 
    kema-CompositeKEM{
      id-MLKEM768-RSA2048-SHA3-256, 
      pk-MLKEM768-RSA2048-SHA3-256 }


id-MLKEM768-RSA3072-SHA3-256 OBJECT IDENTIFIER ::= {
   iso(1) identified-organization(3) dod(6) internet(1) security(5)
   mechanisms(5) pkix(7) alg(6) 56 }

pk-MLKEM768-RSA3072-SHA3-256 PUBLIC-KEY ::= 
  pk-CompositeKEM {
    id-MLKEM768-RSA3072-SHA3-256 }

kema-MLKEM768-RSA3072-SHA3-256 KEM-ALGORITHM ::=
    kema-CompositeKEM{
      id-MLKEM768-RSA3072-SHA3-256, 
      pk-MLKEM768-RSA3072-SHA3-256 }


id-MLKEM768-RSA4096-SHA3-256 OBJECT IDENTIFIER ::= {
   iso(1) identified-organization(3) dod(6) internet(1) security(5)
   mechanisms(5) pkix(7) alg(6) 57 }


pk-MLKEM768-RSA4096-SHA3-256 PUBLIC-KEY ::= 
  pk-CompositeKEM {
    id-MLKEM768-RSA4096-SHA3-256 }

kema-MLKEM768-RSA4096-SHA3-256 KEM-ALGORITHM ::=
    kema-CompositeKEM{
      id-MLKEM768-RSA4096-SHA3-256, 
      pk-MLKEM768-RSA4096-SHA3-256 }



id-MLKEM768-X25519-SHA3-256 OBJECT IDENTIFIER ::= {
   iso(1) identified-organization(3) dod(6) internet(1) security(5)
   mechanisms(5) pkix(7) alg(6) 58 }


pk-MLKEM768-X25519-SHA3-256 PUBLIC-KEY ::= 
  pk-CompositeKEM {
    id-MLKEM768-X25519-SHA3-256 }

kema-MLKEM768-X25519-SHA3-256 KEM-ALGORITHM ::= 
    kema-CompositeKEM{
      id-MLKEM768-X25519-SHA3-256, 
      pk-MLKEM768-X25519-SHA3-256 }


id-MLKEM768-ECDH-P256-SHA3-256 OBJECT IDENTIFIER ::= {
   iso(1) identified-organization(3) dod(6) internet(1) security(5)
   mechanisms(5) pkix(7) alg(6) 59 }


pk-MLKEM768-ECDH-P256-SHA3-256 PUBLIC-KEY ::= 
  pk-CompositeKEM {
    id-MLKEM768-ECDH-P256-SHA3-256 }

kema-MLKEM768-ECDH-P256-SHA3-256 KEM-ALGORITHM ::= 
    kema-CompositeKEM{
      id-MLKEM768-ECDH-P256-SHA3-256, 
      pk-MLKEM768-ECDH-P256-SHA3-256 }


id-MLKEM768-ECDH-P384-SHA3-256 OBJECT IDENTIFIER ::= {
   iso(1) identified-organization(3) dod(6) internet(1) security(5)
   mechanisms(5) pkix(7) alg(6) 60 }


pk-MLKEM768-ECDH-P384-SHA3-256 PUBLIC-KEY ::= 
  pk-CompositeKEM {
    id-MLKEM768-ECDH-P384-SHA3-256 }

kema-MLKEM768-ECDH-P384-SHA3-256 KEM-ALGORITHM ::= 
    kema-CompositeKEM{
      id-MLKEM768-ECDH-P384-SHA3-256, 
      pk-MLKEM768-ECDH-P384-SHA3-256 }


id-MLKEM768-ECDH-brainpoolP256r1-SHA3-256 OBJECT IDENTIFIER ::= {
   iso(1) identified-organization(3) dod(6) internet(1) security(5)
   mechanisms(5) pkix(7) alg(6) 61 }


pk-MLKEM768-ECDH-brainpoolP256r1-SHA3-256 PUBLIC-KEY ::= 
  pk-CompositeKEM {
    id-MLKEM768-ECDH-brainpoolP256r1-SHA3-256 }

kema-MLKEM768-ECDH-brainpoolP256r1-SHA3-256 KEM-ALGORITHM ::= 
    kema-CompositeKEM{
      id-MLKEM768-ECDH-brainpoolP256r1-SHA3-256, 
      pk-MLKEM768-ECDH-brainpoolP256r1-SHA3-256 }


id-MLKEM1024-RSA3072-SHA3-256 OBJECT IDENTIFIER ::= {
   iso(1) identified-organization(3) dod(6) internet(1) security(5)
   mechanisms(5) pkix(7) alg(6) 62 }


pk-MLKEM1024-RSA3072-SHA3-256 PUBLIC-KEY ::= 
  pk-CompositeKEM {
    id-MLKEM1024-RSA3072-SHA3-256 }

kema-MLKEM1024-RSA3072-SHA3-256 KEM-ALGORITHM ::=
    kema-CompositeKEM{
      id-MLKEM1024-RSA3072-SHA3-256,
      pk-MLKEM1024-RSA3072-SHA3-256 }


id-MLKEM1024-ECDH-P384-SHA3-256 OBJECT IDENTIFIER ::= {
   iso(1) identified-organization(3) dod(6) internet(1) security(5)
   mechanisms(5) pkix(7) alg(6) 63 }


pk-MLKEM1024-ECDH-P384-SHA3-256 PUBLIC-KEY ::= 
  pk-CompositeKEM {
    id-MLKEM1024-ECDH-P384-SHA3-256 }

kema-MLKEM1024-ECDH-P384-SHA3-256 KEM-ALGORITHM ::= 
    kema-CompositeKEM{
      id-MLKEM1024-ECDH-P384-SHA3-256, 
      pk-MLKEM1024-ECDH-P384-SHA3-256 }


id-MLKEM1024-ECDH-brainpoolP384r1-SHA3-256 OBJECT IDENTIFIER ::= {
   iso(1) identified-organization(3) dod(6) internet(1) security(5)
   mechanisms(5) pkix(7) alg(6) 64 }


pk-MLKEM1024-ECDH-brainpoolP384r1-SHA3-256 PUBLIC-KEY ::= 
  pk-CompositeKEM{
    id-MLKEM1024-ECDH-brainpoolP384r1-SHA3-256 }

kema-MLKEM1024-ECDH-brainpoolP384r1-SHA3-256 KEM-ALGORITHM ::= 
    kema-CompositeKEM{
      id-MLKEM1024-ECDH-brainpoolP384r1-SHA3-256, 
      pk-MLKEM1024-ECDH-brainpoolP384r1-SHA3-256 }
      

id-MLKEM1024-X448-SHA3-256 OBJECT IDENTIFIER ::= {
   iso(1) identified-organization(3) dod(6) internet(1) security(5)
   mechanisms(5) pkix(7) alg(6) 65 }


pk-MLKEM1024-X448-SHA3-256 PUBLIC-KEY ::= 
  pk-CompositeKEM {
    id-MLKEM1024-X448-SHA3-256 }

kema-MLKEM1024-X448 KEM-ALGORITHM ::= 
    kema-CompositeKEM{
      id-MLKEM1024-X448-SHA3-256, 
      pk-MLKEM1024-X448-SHA3-256 }


id-MLKEM1024-ECDH-P521-SHA3-256 OBJECT IDENTIFIER ::= {
   iso(1) identified-organization(3) dod(6) internet(1) security(5)
   mechanisms(5) pkix(7) alg(6) 66 }


pk-MLKEM1024-ECDH-P521-SHA3-256 PUBLIC-KEY ::= 
  pk-CompositeKEM {
    id-MLKEM1024-ECDH-P521-SHA3-256 }

kema-MLKEM1024-ECDH-P521-SHA3-256 KEM-ALGORITHM ::= 
    kema-CompositeKEM{
      id-MLKEM1024-ECDH-P521-SHA3-256, 
      pk-MLKEM1024-ECDH-P521-SHA3-256 }

PublicKeys PUBLIC-KEY ::= {
   -- This expands PublicKeyAlgorithms from [RFC 5912]
   pk-MLKEM768-RSA2048-SHA3-256 |
   pk-MLKEM768-RSA3072-SHA3-256 |
   pk-MLKEM768-RSA4096-SHA3-256 |
   pk-MLKEM768-X25519-SHA3-256 |
   pk-MLKEM768-ECDH-P256-SHA3-256 |
   pk-MLKEM768-ECDH-P384-SHA3-256 |
   pk-MLKEM768-ECDH-brainpoolP256r1-SHA3-256 |
   pk-MLKEM1024-RSA3072-SHA3-256 |
   pk-MLKEM1024-ECDH-P384-SHA3-256 |
   pk-MLKEM1024-ECDH-brainpoolP384r1-SHA3-256 |
   pk-MLKEM1024-X448-SHA3-256 |
   pk-MLKEM1024-ECDH-P521-SHA3-256,
   ...
}

END
