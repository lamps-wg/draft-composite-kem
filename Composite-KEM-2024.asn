Composite-KEM-2024
      {iso(1) identified-organization(3) dod(6) internet(1) 
        security(5) mechanisms(5) pkix(7) id-mod(0) 
        id-mod-composite-kems(TBDMOD) }

DEFINITIONS IMPLICIT TAGS ::= BEGIN

EXPORTS ALL;

IMPORTS

PUBLIC-KEY, AlgorithmIdentifier{}, SMIME-CAPS
  FROM AlgorithmInformation-2009  -- RFC 5912 [X509ASN1]
      { iso(1) identified-organization(3) dod(6) internet(1)
        security(5) mechanisms(5) pkix(7) id-mod(0)
        id-mod-algorithmInformation-02(58) }

KEM-ALGORITHM
  FROM KEMAlgorithmInformation-2023
      { iso(1) identified-organization(3) dod(6) internet(1)
        security(5) mechanisms(5) pkix(7) id-mod(0)
        id-mod-kemAlgorithmInformation-2023(99) }

SubjectPublicKeyInfo
  FROM PKIX1Explicit-2009
      { iso(1) identified-organization(3) dod(6) internet(1)
        security(5) mechanisms(5) pkix(7) id-mod(0)
        id-mod-pkix1-explicit-02(51) }

OneAsymmetricKey
    FROM AsymmetricKeyPackageModuleV1
      { iso(1) member-body(2) us(840) rsadsi(113549) pkcs(1)
        pkcs-9(9) smime(16) modules(0)
        id-mod-asymmetricKeyPkgV1(50) }

RSAPublicKey, ECPoint
  FROM PKIXAlgs-2009 
    { iso(1) identified-organization(3) dod(6)
      internet(1) security(5) mechanisms(5) pkix(7) id-mod(0)
      id-mod-pkix1-algorithms2008-02(56) }

;


--
-- Object Identifiers
--

-- Defined in ITU-T X.690
der OBJECT IDENTIFIER ::=
  {joint-iso-itu-t asn1(1) ber-derived(2) distinguished-encoding(1)}



--
-- Composite KEM basic structures
--

CompositeKEMPublicKey ::= SEQUENCE SIZE (2) OF BIT STRING

CompositeKEMPublicKeyOs ::= OCTET STRING (CONTAINING 
                                CompositeKEMPublicKey ENCODED BY der)

CompositeKEMPublicKeyBs ::= BIT STRING (CONTAINING 
                                CompositeKEMPublicKey ENCODED BY der)

CompositeKEMPrivateKey ::= SEQUENCE SIZE (2) OF OneAsymmetricKey

CompositeCiphertextValue ::= SEQUENCE SIZE (2) OF OCTET STRING


--
-- Information Object Classes
--

pk-CompositeKEM {
  OBJECT IDENTIFIER:id, FirstPublicKeyType,
  SecondPublicKeyType} PUBLIC-KEY ::=
  {
    IDENTIFIER id
    KEY SEQUENCE {
    first BIT STRING (CONTAINING FirstPublicKeyType),
    second BIT STRING (CONTAINING SecondPublicKeyType)
    }
    PARAMS ARE absent
    CERT-KEY-USAGE { keyEncipherment }
  }

kema-CompositeKEM {
  OBJECT IDENTIFIER:id, 
    PUBLIC-KEY:publicKeyType } 
    KEM-ALGORITHM ::= {
         IDENTIFIER id
         VALUE CompositeCiphertextValue
         PARAMS ARE absent
         PUBLIC-KEYS { publicKeyType } 
         SMIME-CAPS { IDENTIFIED BY id }
        }



--
-- Composite KEM Algorithms
--


-- TODO: OID to be replaced by IANA
id-MLKEM768-RSA2048 OBJECT IDENTIFIER ::= {
  joint-iso-itu-t(2) country(16) us(840) organization(1) 
  entrust(114027) algorithm(80) explicitcomposite(5) kem(2) 13 }

pk-MLKEM768-RSA2048 PUBLIC-KEY ::= 
  pk-CompositeKEM { 
    id-MLKEM512-RSA2048, 
    OCTET STRING, RSAPublicKey }

kema-MLKEM768-RSA2048 KEM-ALGORITHM ::= 
    kema-CompositeKEM{
      id-MLKEM512-RSA2048, 
      pk-MLKEM512-RSA2048 }



-- TODO: OID to be replaced by IANA
id-MLKEM768-RSA3072 OBJECT IDENTIFIER ::= {
  joint-iso-itu-t(2) country(16) us(840) organization(1) 
  entrust(114027) algorithm(80) explicitcomposite(5) kem(2) 4 }

pk-MLKEM768-RSA3072 PUBLIC-KEY ::= 
  pk-CompositeKEM {
    id-MLKEM512-RSA3072, 
    OCTET STRING, RSAPublicKey }

kema-MLKEM768-RSA3072 KEM-ALGORITHM ::=
    kema-CompositeKEM{
      id-MLKEM512-RSA3072, 
      pk-MLKEM512-RSA3072 }



-- TODO: OID to be replaced by IANA
id-MLKEM768-RSA4096 OBJECT IDENTIFIER ::= {
  joint-iso-itu-t(2) country(16) us(840) organization(1) 
  entrust(114027) algorithm(80) explicitcomposite(5) kem(2) TBD }

pk-MLKEM768-RSA4096 PUBLIC-KEY ::= 
  pk-CompositeKEM {
    id-MLKEM512-RSA4096, 
    OCTET STRING, RSAPublicKey }

kema-MLKEM768-RSA4096 KEM-ALGORITHM ::=
    kema-CompositeKEM{
      id-MLKEM512-RSA4096, 
      pk-MLKEM512-RSA4096 }


-- TODO: OID to be replaced by IANA
id-MLKEM768-ECDH-P384 OBJECT IDENTIFIER ::= {
  joint-iso-itu-t(2) country(16) us(840) organization(1) 
  entrust(114027) algorithm(80) explicitcomposite(5) kem(2) 5 }

pk-MLKEM768-ECDH-P384 PUBLIC-KEY ::= 
  pk-CompositeKEM {
    id-MLKEM768-ECDH-P384, 
    OCTET STRING, ECPoint }

kema-MLKEM768-ECDH-P384 KEM-ALGORITHM ::= 
    kema-CompositeKEM{
      id-MLKEM768-ECDH-P384, 
      pk-MLKEM768-ECDH-P384 }


-- TODO: OID to be replaced by IANA
id-MLKEM768-ECDH-brainpoolP256r1 OBJECT IDENTIFIER ::= {
  joint-iso-itu-t(2) country(16) us(840) organization(1) 
  entrust(114027) algorithm(80) explicitcomposite(5) kem(2) 6 }

pk-MLKEM768-ECDH-brainpoolP256r1 PUBLIC-KEY ::= 
  pk-CompositeKEM {
    id-MLKEM768-ECDH-brainpoolP256r1, 
    OCTET STRING, ECPoint }

kema-MLKEM768-ECDH-brainpoolP256r1 KEM-ALGORITHM ::= 
    kema-CompositeKEM{
      id-MLKEM768-ECDH-brainpoolP256r1, 
      pk-MLKEM768-ECDH-brainpoolP256r1 }


-- TODO: OID to be replaced by IANA
id-MLKEM768-X25519 OBJECT IDENTIFIER ::= {
  joint-iso-itu-t(2) country(16) us(840) organization(1)
  entrust(114027) algorithm(80) explicitcomposite(5) kem(2) 7 }

pk-MLKEM768-X25519 PUBLIC-KEY ::= 
  pk-CompositeKEM {
    id-MLKEM768-X25519, 
    OCTET STRING, OCTET STRING }

kema-MLKEM768-X25519 KEM-ALGORITHM ::= 
    kema-CompositeKEM{
      id-MLKEM768-X25519, 
      pk-MLKEM768-X25519 }



-- TODO: OID to be replaced by IANA
id-MLKEM1024-ECDH-P384 OBJECT IDENTIFIER ::= {
  joint-iso-itu-t(2) country(16) us(840) organization(1)
  entrust(114027) algorithm(80) explicitcomposite(5) kem(2) 8 }

pk-MLKEM1024-ECDH-P384 PUBLIC-KEY ::= 
  pk-CompositeKEM {
    id-MLKEM1024-ECDH-P384, 
    OCTET STRING, ECPoint }

kema-MLKEM1024-ECDH-P384 KEM-ALGORITHM ::= 
    kema-CompositeKEM{
      id-MLKEM1024-ECDH-P384, 
      pk-MLKEM1024-ECDH-P384 }


-- TODO: OID to be replaced by IANA
id-MLKEM1024-ECDH-brainpoolP384r1 OBJECT IDENTIFIER ::= {
  joint-iso-itu-t(2) country(16) us(840) organization(1) 
  entrust(114027) algorithm(80) explicitcomposite(5) kem(2) 9 }

pk-MLKEM1024-ECDH-brainpoolP384r1 PUBLIC-KEY ::= 
  pk-CompositeKEM{
    id-MLKEM1024-ECDH-brainpoolP384r1, 
    OCTET STRING, ECPoint }

kema-MLKEM1024-ECDH-brainpoolP384r1 KEM-ALGORITHM ::= 
    kema-CompositeKEM{
      id-MLKEM1024-ECDH-brainpoolP384r1, 
      pk-MLKEM1024-ECDH-brainpoolP384r1 }
      

-- TODO: OID to be replaced by IANA
id-MLKEM1024-X448 OBJECT IDENTIFIER ::= {
  joint-iso-itu-t(2) country(16) us(840) organization(1) 
  entrust(114027) algorithm(80) explicitcomposite(5) kem(2) 10 }

pk-MLKEM1024-X448 PUBLIC-KEY ::= 
  pk-CompositeKEM {
    id-MLKEM1024-X448, 
    OCTET STRING, OCTET STRING }

kema-MLKEM1024-X448 KEM-ALGORITHM ::= 
    kema-CompositeKEM{
      id-MLKEM1024-X448, 
      pk-MLKEM1024-X448 }


--
-- Expand the S/MIME capabilities set used by CMS [RFC5911]
--

SMimeCaps SMIME-CAPS ::=
    { kema-MLKEM512-ECDH-P256-KMAC128.&smimeCaps |
      kema-MLKEM512-ECDH-brainpoolP256r1-KMAC128.&smimeCaps |
      kema-MLKEM512-X25519-KMAC128.&smimeCaps |
      kema-MLKEM512-RSA2048-KMAC128.&smimeCaps |
      kema-MLKEM512-RSA3072-KMAC128.&smimeCaps |
      kema-MLKEM768-ECDH-P256-KMAC256.&smimeCaps |
      kema-MLKEM768-ECDH-brainpoolP256r1-KMAC256.&smimeCaps |
      kema-MLKEM768-X25519-KMAC256.&smimeCaps |
      kema-MLKEM1024-ECDH-P384-KMAC256.&smimeCaps |
      kema-MLKEM1024-ECDH-brainpoolP384r1-KMAC256.&smimeCaps |
      kema-MLKEM1024-X448-KMAC256.&smimeCaps,
      ... }

END
